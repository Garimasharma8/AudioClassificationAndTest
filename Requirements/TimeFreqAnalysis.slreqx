# TimeFreqAnalysis
Requirements to test in time and frequency domain analysis

## #2: Time Domain Analysis (Functional)

### #4: Peak Amplitude (Functional)

### #6: RMS Amplitude (Functional)

### #7: RMS DBFS (Functional)

### #8: ZCR (Functional)

## #3: Frequency Domain Analysis (Functional)

### #10: Test Peak Frequency (Functional)
Peak frequency must be less than the Nyquist frequency which is half of the sampling frequency.

### #12: Pitch of audio (Functional)

### #13: Fundamental freq range (Functional)

### #14: FFT of signal (Functional)

## #11: Classification test (Functional)
